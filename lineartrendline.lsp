(defun _lineartrendline ( l / a ax ay b f x y )
   (setq f '(( l ) (/ (apply '+ l) (length l)))
         x  (mapcar 'car  l)
         y  (mapcar 'cadr l)
         ax (f x)
         ay (f y)
         b  (/ (- (f (mapcar '* x y)) (* ax ay))
               (- (f (mapcar '* x x)) (* ax ax))
            )
         a  (- ay (* b ax))
   )
   (entmake
       (list
          '(000 . "RAY")
          '(100 . "AcDbEntity")
          '(100 . "AcDbRay")
           (list 10 0.0 a 0.0)
           (list 11 1.0 b 0.0)
       )
   )
)
