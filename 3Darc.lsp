(defun c:3Darc (/ p1 p2 p3)
 (command "_ucs" "_w")
 (setq p1 (getpoint "Arc point #1: "))
 (setq p2 (getpoint "Arc point #2: "))
 (setq p3 (getpoint "Arc point #3: "))
 (command "_ucs" "_3p" p1 p2 p3)
 (command "_arc" (trans p1 0 1)(trans p2 0 1)(trans p3 0 1))
 (command "_ucs" "_p")
)
resp.:
(defun c:3Dcircle (/ p1 p2 p3)
 (command "_ucs" "_w")
 (setq p1 (getpoint "Circle point #1: "))
 (setq p2 (getpoint "Circle point #2: "))
 (setq p3 (getpoint "Circle point #3: "))
 (command "_ucs" "_3p" p1 p2 p3)
 (command "_circle" "_3p" (trans p1 0 1)(trans p2 0 1)(trans p3 0 1))
 (command "_ucs" "_p")
)
